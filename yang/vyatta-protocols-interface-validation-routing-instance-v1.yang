module vyatta-protocols-interface-validation-routing-instance-v1 {
	namespace "urn:vyatta.com:mgmt:vyatta-protocols-interface-validation-routing-instance:1";
	prefix vyatta-protocols-interface-validation-routing-instance-v1;

	import vyatta-interfaces-v1 {
		prefix if;
	}
	import vyatta-routing-instance-interfaces-v1 {
		prefix vyatta-routing-instance-if-v1;
	}
	import configd-v1 {
		prefix configd;
	}

	organization "AT&T, Inc.";
	contact
		"AT&T
		 Postal: 208 S. Akard Street
				 Dallas, TX 75202
		 Web: www.att.com";

	description
		"Copyright (c) 2018-2019, AT&T Intellectual Property.
		 All rights reserved.

		 Copyright (c) 2016-2017 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module package for
		 vyatta-protocols-interface-validation-routing-instance-v1";

	revision 2019-03-22 {
		description
			"Add custom must statement for efficiency when validating
             interface leafrefs.";
	}
	revision 2018-11-14 {
		description "Update organization, contact, description";
	}

	revision 2017-01-05 {
		description "Add enumeration type for passive-interface ";
	}

	revision 2016-05-25 {
		description "Initial revision of version 1";
	}

	/*
	 * The following groupings originate from OSPFv2/v3 protocols.
	 * Other protocols are free to use them or embed their
	 * own "must" statements.
	 */
	grouping ospf-passive-intf-routing-inst {
		leaf-list passive-interface {
			/*
			 * Leafref uses relative path, used in both OSPF and
			 * OSPFv3 - re-use grouping with caution.
			 */
			type union {
				type string;
				type enumeration {
					enum "default" {
						configd:help "Suppress routing updates on all interfaces";
						description "Suppress routing updates on all interfaces";
					}
				}
			}
			ordered-by "user";
			must "not( (current() = 'default') and (count(../passive-interface) > 1))" {
				error-message "Can't configure passive-interface 'default' with other interfaces";
			}
			must "((current() = 'default') or (current() = /if:interfaces/*/*[(local-name(.) = 'tagnode') or (local-name(.) = 'ifname')] "
			+ "or /if:interfaces/*/*[local-name(.) = 'vif'][./../* = substring-before(current(), '.')]"
			+ "/*[(local-name(.) = 'tagnode') or (local-name(.) = 'ifname')][. = substring-after(current(), '.')]))" {
				error-message "Invalid interface name";
				configd:must "current() = 'default' or is-interface-leafref-original(.)";
			}
		}
	}

	grouping ospf-passive-intf-exclude-routing-inst {
		leaf-list passive-interface-exclude {
			/*
			 * Leafref uses relative path, used in both OSPF and
			 * OSPFv3 - re-use grouping with caution.
			 */
			type leafref {
				path "../../../../vyatta-routing-instance-if-v1:interface/vyatta-routing-instance-if-v1:name";
			}
			ordered-by "user";
			must "(../passive-interface = 'default')" {
				error-message "Can't configure passive-interface-exclude without configuring passive-interface 'default'";
			}
		}
	}
}
