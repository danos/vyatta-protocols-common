module vyatta-protocols-interface-validation-v1 {
	namespace "urn:vyatta.com:mgmt:vyatta-protocols-interface-validation:1";
	prefix vyatta-protocols-interface-validation-v1;

	import vyatta-interfaces-v1 {
		prefix if;
	}
	import configd-v1 {
		prefix configd;
	}

	organization "AT&T, Inc.";
	contact
		"AT&T
		 Postal: 208 S. Akard Street
				 Dallas, TX 75202
		 Web: www.att.com";

	description
		"Copyright (c) 2018-2019, AT&T Intellectual Property.
		 All rights reserved.

		 Copyright (c) 2016 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module package for vyatta-protocols-interface-validation-v1";

	revision 2019-03-22 {
		description
			"Add custom must statements for efficiency when validating
             interface leafrefs.";
	}

	revision 2018-11-14 {
		description "Update organization, contact, description";
	}

	revision 2016-07-21 {
		description "Removing peer-address grouping that was used by BGP,
			Move mpls interface out of common file,
			Remove RIP/RIPng specific groupings as the interface names
			used in RIP/RIPng no longer need to be validated against existing
			interfaces,
			Renaming of passive-interface and passive-interface-exclude 
			grouping of OSPF to IGP,
			Add mpls interface support";
	}
	
	revision 2016-01-21 {
		description "Initial revision of version 1";
	}


	grouping interface-common {
		leaf interface {
			type string;
			must "(current() = /if:interfaces/*/*[(local-name(.) = 'tagnode') or (local-name(.) = 'ifname')] "
				+ "or /if:interfaces/*/*[local-name(.) = 'vif'][./../* = substring-before(current(), '.')]"
				+ "/*[(local-name(.) = 'tagnode') or (local-name(.) = 'ifname')][. = substring-after(current(), '.')])" {
				error-message "Interface name must refer to an existing interface name";
				configd:must "is-interface-leafref-original(.)";
			}
		}
	}

	grouping igp-passive-interface {
		leaf-list passive-interface {
			type union {
				type enumeration {
					enum "default";
				}
				type string;
			}
			configd:allowed "/opt/vyatta/sbin/vyatta-interfaces.pl --show all --filter-out ^ers";
			ordered-by "user";
			must "not( (current() = 'default') and (count(../passive-interface) > 1))" {
				error-message "Can't configure passive-interface 'default' with other interfaces";
			}
			must "current() = 'default' or (current() = /if:interfaces/*/*[(local-name(.) = 'tagnode') or (local-name(.) = 'ifname')] "
				+ "or /if:interfaces/*/*[local-name(.) = 'vif'][./../* = substring-before(current(), '.')]"
				+ "/*[(local-name(.) = 'tagnode') or (local-name(.) = 'ifname')][. = substring-after(current(), '.')])" {
				error-message "Invalid interface name";
				configd:must "current() = 'default' or "
					+ "is-interface-leafref-original(.)";
			}
		}
	}

	grouping igp-passive-interface-exclude {
		leaf-list passive-interface-exclude {
			type string;
			configd:allowed "/opt/vyatta/sbin/vyatta-interfaces.pl --show all --filter-out ^ers";
			ordered-by "user";
			must "(../passive-interface = 'default')" {
				error-message "Can't configure passive-interface-exclude without configuring passive-interface 'default'";
			}
			must "(current() = /if:interfaces/*/*[(local-name(.) = 'tagnode') or (local-name(.) = 'ifname')] "
				+ "or /if:interfaces/*/*[local-name(.) = 'vif'][./../* = substring-before(current(), '.')]"
				+ "/*[(local-name(.) = 'tagnode') or (local-name(.) = 'ifname')][. = substring-after(current(), '.')])" {
				error-message "Invalid interface name";
				configd:must "is-interface-leafref-original(.)";
			}
		}
	}
}
