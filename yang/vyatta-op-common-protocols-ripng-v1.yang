module vyatta-op-common-protocols-ripng-v1 {
    namespace "urn:vyatta.com:mgmt:vyatta-op-common-protocols-ripng:1";
    prefix vyatta-op-common-protocols-ripng-v1;

    import vyatta-opd-extensions-v1 {
        prefix opd;
    }
    import vyatta-op-show-v1 {
        prefix op-show;
    }
    import vyatta-op-show-ip-ipv6-v1 {
        prefix op-show-ip-ipv6;
    }
    import vyatta-op-show-ip-ipv6-route-v1 {
        prefix op-show-ip-ipv6-route;
    }

    organization "AT&T, Inc.";
    contact
        "AT&T
         Postal: 208 S. Akard Street
                 Dallas, TX 75202
         Web: www.att.com";

    description
        "Copyright (c) 2019, AT&T Intellectual Property.
         All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

         This module implements the common RIPNG show CLI";

    revision 2019-05-24 {
        description "Initial revision";
    }

    grouping show-ip-route-ripng-commands {
        opd:command ripng {
            opd:help "Show IP RIPNG routes";
        }
    }

    opd:augment /op-show:show/op-show-ip-ipv6:ipv6/op-show-ip-ipv6-route:route {
        uses show-ip-route-ripng-commands;
    }
}
