module vyatta-protocols-static-routing-instance-v1 {
	namespace "urn:vyatta.com:mgmt:vyatta-protocols-static-routing-instance:1";
	prefix vyatta-protocols-static-routing-instance-v1;

	import vyatta-routing-v1 {
		prefix vyatta-routing;
	}
	import vyatta-protocols-static-v1 {
		prefix vyatta-static;
	}
	import vyatta-routing-instance-interfaces-v1 {
		prefix routing-instance-if;
	}

	organization "AT&T, Inc.";
	contact
		"AT&T
		 Postal: 208 S. Akard Street
		         Dallas, TX 75202
		 Web: www.att.com";

	description
		"Copyright (c) 2018-2019, AT&T Intellectual Property.
		 All rights reserved.

		 Copyright (c) 2016 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module package for
		 vyatta-protocols-static-route-routing-instance-v1";

	revision 2018-11-14 {
		description "Add static-pbr-tables feature.
			Update organization and contact.";
	}
	revision 2016-05-01 {
		description "Initial revision of version 1";
	}

	feature static-pbr-tables {
		description "Support for multiple static PBR tables in routing instances";
	}

	augment /vyatta-routing:routing/vyatta-routing:routing-instance/vyatta-routing:protocols {
		uses vyatta-static:static-container;
	}

	augment /vyatta-routing:routing/vyatta-routing:routing-instance/vyatta-routing:protocols/static {
		uses vyatta-static:static-route-pbr-tables {
			if-feature static-pbr-tables;
		}
		uses vyatta-static:static-route-main-table {
			refine route/next-hop/interface {
				must "(1 = count(/vyatta-routing:routing/vyatta-routing:routing-instance[vyatta-routing:instance-name =
					current()/../../../../../vyatta-routing:instance-name]/routing-instance-if:interface[routing-instance-if:name = current()]))" {
					error-message "next-hop interface doesn't belong to routing-instance";
				}
			}
			refine route6/next-hop/interface {
				must "(1 = count(/vyatta-routing:routing/vyatta-routing:routing-instance[vyatta-routing:instance-name =
					current()/../../../../../vyatta-routing:instance-name]/routing-instance-if:interface[routing-instance-if:name = current()]))" {
					error-message "next-hop interface doesn't belong to routing-instance";
				}
			}
		}
	}
}
